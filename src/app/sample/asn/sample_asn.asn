-- $Id$
-- By D. Vakatov, NCBI
--
-- A very simple ASN.1 spec for demo purposes only


NCBI-Sample-ASN  DEFINITIONS ::=

BEGIN

IMPORTS Date, Object-id FROM NCBI-General;


--
-- Some simple type
--

NCBI-Sample-ASN-Type  ::= SEQUENCE {
    date    Date,
    id      Object-id,
    name    VisibleString OPTIONAL,
    tag     INTEGER DEFAULT 999
}


END


--
-- $Log: sample_asn.asn,v $
-- Revision 1.1  2006/11/24 23:46:03  vakatov
-- Initial revision
--
--
