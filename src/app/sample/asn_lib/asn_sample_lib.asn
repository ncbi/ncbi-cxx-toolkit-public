-- This is only a demo

NCBI-sample DEFINITIONS ::=
BEGIN

EXPORTS Data-set-id;

Data-set-id ::= SEQUENCE {
    version       VisibleString,
    name          UTF8String,
    num           INTEGER ,
    type          INTEGER {
        dump   (1),
        query  (2),
       	single (3) } ,
    weight        REAL  OPTIONAL,
    uids          SEQUENCE OF INTEGER OPTIONAL
}

END
